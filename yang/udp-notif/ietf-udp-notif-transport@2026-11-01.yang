module ietf-udp-notif-transport {
  yang-version 1.1;
  namespace "urn:ietf:params:xml:ns:yang:ietf-udp-notif-transport";
  prefix unt;

  import ietf-subscribed-notifications {
    prefix sn;
    reference
      "RFC 8639: Subscription to YANG Notifications";
  }
  import ietf-subscribed-notif-receivers {
    prefix snr;
    reference
      "draft-ietf-netconf-https-notif: An HTTPS-based Transport for
       YANG Notifications";
  }
  import ietf-udp-client {
    prefix udpc;
    reference
      "RFC 9984: YANG Grouping for UDP Clients and UDP Servers";
  }
  import ietf-tls-client {
    prefix tlsc;
    reference
      "RFC 9645: YANG Groupings for TLS Clients and TLS Servers";
  }

  organization
    "IETF NETCONF (Network Configuration) Working Group";
  contact
    "WG Web:   <https://datatracker.ietf.org/wg/netconf/>
     WG List:  <mailto:netconf@ietf.org>

     Authors:  Tianran Zhou
               <mailto:zhoutianran@huawei.com>
               Thomas Graf
               <mailto:thomas.graf@swisscom.com>
               Pierre Francois
               <mailto:pierre.francois@insa-lyon.fr>
               Alex Huang Feng
               <mailto:alex.huang-feng@t-systems.com>
               Paolo Lucente
               <mailto:paolo@ntt.net>";

  description
    "Defines a model for configuring UDP-Notif as a transport
     for configured subscriptions [RFC8639].

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision 2026-11-01 {
    description
      "Initial revision";
    reference
      "RFC XXXX: UDP-based Transport for Configured Subscriptions";
  }

  /*
   * FEATURES
   */

  feature encode-cbor {
    description
      "Indicates that CBOR encoding of notification
       messages is supported.";
    reference
      "RFC 9254: CBOR Encoding of Data Modeled with YANG";
  }

  feature dtls {
    description
      "Indicates that DTLS encryption of UDP-Notif messages
       is supported.";
    reference
      "RFC 6347: Datagram Transport Layer Security Version 1.2,
       RFC 9147: The Datagram Transport Layer Security (DTLS)
       Protocol Version 1.3";
  }

  /*
   * IDENTITIES
   */  

  identity udp-notif {
    base sn:transport;
    base sn:configurable-encoding;
    description
      "UDP-Notif is used as transport for notification messages
       and subscription state change notifications.";
  }

  identity encode-cbor {
    base sn:encoding;
    if-feature "encode-cbor";
    description
      "Encode data using CBOR.";
    reference
      "RFC 9254: CBOR Encoding of Data Modeled with YANG";
  }

  grouping udp-notif-receiver {
    description
      "Provides a reusable identification of a UDP-Notif target
       receiver.";
    uses udpc:udp-client {
      refine "remote-port" {
        mandatory true;
      }
    }
    container dtls {
      if-feature "dtls";
      presence "dtls";
      uses tlsc:tls-client-grouping {
        // Remove keep-alives for DTLS
        refine "keepalives" {
          if-feature "not tlsc:tls-client-keepalives";
        }
      }
      description
        "Container for configuring DTLS parameters.";
    }
    leaf enable-segmentation {
      type boolean;
      default "true";
      description
        "When disabled, the publisher will not segment UDP-Notif
         messages and restrict the size of individual messages to the
         IP-layer MTU. Messages larger then the MTU of the egress
         interface will be dropped. Disabling is therefore not
         recommended.";
    }
    leaf max-segment-size {
      type uint16 {
        range "16..max" {
          description
            "The minimum value of 16 octets corresponds to an empty
             UDP-Notif segment, consisting of the 12-octet fixed
             header and the 4-octet segmentation option, without
             any notification payload.";
        }
      }
      description
        "UDP-Notif provides a configurable max-segment-size to
         control the size of each segment (UDP-Notif header, with
         options, included).

         No default value is defined because the maximum segment
         size depends on the underlying IP version (IPv4 or IPv6),
         the path MTU, and whether DTLS is enabled. When DTLS is
         enabled, the overhead also depends on the DTLS version
         and negotiated cryptographic parameters.

         The operator is responsible for configuring a value
         that ensures the resulting IP datagram does not exceed
         the path MTU to the receiver.";
    }
  }

  augment "/sn:subscriptions/snr:receiver-instances/"
        + "snr:receiver-instance/snr:transport-type" {
    case udp-notif {
      container udp-notif-receiver {
        description
          "The UDP-Notif receiver to send notifications to.";
        uses udp-notif-receiver;
      }
    }
    description
      "Augments the transport-type choice to include the 'udp-notif'
       transport.";
  }
}
